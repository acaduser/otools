(defun c:verticalScale (/ *error* main scaleY doc UcsChanged Scale kw)
	(vl-load-com)
	(defun main(/ loop)
		(princ "\nverticalScale")
		(vla-StartUndoMark (setq doc (vla-get-ActiveDocument (vlax-get-acad-object))))
		(setvar "cmdecho" 0)
		(if (setq ss (ssget "_:L" '((0 . "LINE,LWPOLYLINE,CIRCLE,TEXT,INSERT,DIMENSION"))))
			(progn		
				(initget 1)
				(setq pt1u (getpoint "\n基点:"))
				(setq pt1w (trans pt1u 1 0))
				(setq pt1wXY (list (car pt1w) (cadr pt1w) 0.0))
				(setq loop t)
				(while loop
					(initget 1)
					(setq pt2u (getpoint (trans pt1wXY 0 1) "\nXの正方向:"))
					(setq pt2w (trans pt2u 1 0))
					(setq pt2wXY (list (car pt2w) (cadr pt2w) 0.0))
					(if (not (equal pt1wXY pt2wXY))
						(setq loop nil)
					)
				)
				(command "_.ucs" "_3p" "_non" (trans pt1wXY 0 1) "_non" (trans pt2wXY 0 1) "")
				(setq ucsChanged t)
				(initget 7 "r")
				(setq res (getreal "\n尺度を指定[参照(R)]:"))
				(print res)
				(cond
					((numberp res)
						(setq scale res)
					)
					((= res "r")
						(initget 1)
						(setq pt1u (getpoint "\n参照1点目:"))
						(initget 1)
						(setq pt2u (getpoint pt1u "\n参照2点目:"))
						(initget 1)
						(setq pt3u (getpoint pt1u "\n新しい長さ指定:"))
						(setq scale (/ (distance pt1u pt3u) (distance pt1u pt2u)))
					)
				)
				(initget 6 "Y N")
				(setq kw (getkword "\nオブジェクトを各々尺度変更[(Y)/(N)]<Y>:"))
				(if (null kw) (setq kw "Y"))
				(setq i 0)
				(repeat (sslength ss)
					(setq ename (ssname ss i))
					(setq oname (cdr (assoc 0 (entget ename))))
					(cond
						((= oname "LINE") (mod-line ename))
						((= oname "LWPOLYLINE") (mod-lwpolyline ename))
						((= oname "CIRCLE") (mod-circle ename))
						((= oname "TEXT") (mod-text ename))
						((= oname "INSERT") (mod-insert ename))
						((= oname "DIMENSION") (mod-dimension ename))
						(t nil)
					)
					(setq i (1+ i))
				)
			)
		)
		(if ucsChanged (if command-s (command-s "_.ucs" "_p") (command "_.ucs" "_p")))
		(vla-EndUndoMark doc)
		(princ)
	)
	(defun mod-line (ename / data )
		(setq pt1w (cdr (assoc 10 (entget ename))))
		(setq pt2w (cdr (assoc 11 (entget ename))))
		(setq data (entget ename))
		(setq data (subst (cons 10 (scaleY pt1w)) (assoc 10 data) data))
		(setq data (subst (cons 11 (scaleY pt2w)) (assoc 11 data) data))
		(entmod data)
	)
	(defun mod-lwpolyline (ename / data tmp )
		(setq obj (vlax-ename->vla-object ename))
		(setq coords (vlax-safearray->list (vlax-variant-value (vla-get-Coordinates obj))))
		(setq len (length coords))
		(while coords
			(setq pt (list (car coords) (cadr coords)))
			(setq newPt (reverse (cdr (reverse (scaleY pt)))))
			(setq tmp (cons newPt tmp))
			(setq coords (cddr coords))
		)
		(setq sa (vlax-make-safearray vlax-vbDouble (cons 0 (1- len))))
		(vlax-safearray-fill sa (apply 'append (reverse tmp)))
		(vla-put-Coordinates obj sa)
		(vla-Update obj)
	)
	(defun mod-circle (ename / data)
		(setq obj (vlax-ename->vla-object ename))
		(setq ptw (vlax-safearray->list (vlax-variant-value (vla-get-Center obj))))
		(vla-put-Center obj (vlax-3d-point (scaleY ptw)))
		(if (= kw "Y")
			(progn
				(vla-put-Radius obj (* (vla-get-Radius obj) scale))
			)
		)
		(vla-Update obj)
	)
	(defun mod-text (ename / data)
		(setq obj (vlax-ename->vla-object ename))
		(setq data (entget ename))
		(setq pt1w (cdr (assoc 10 data)))
		(setq pt2w (cdr (assoc 11 data)))
		(setq data (subst (cons 10 (scaleY pt1w)) (assoc 10 data) data))
		(setq data (subst (cons 11 (scaleY pt2w)) (assoc 11 data) data))
		(entmod data)
		(if (= kw "Y")
			(progn
				(vla-put-Height obj (* (vla-get-Height obj) scale))
			)
		)
		(vla-Update obj)
	)
	(defun mod-insert (ename / data obj scx scy scz)
		(setq data (entget ename))
		(setq obj (vlax-ename->vla-object ename))
		(setq ptw (cdr (assoc 10 data)))
		(vla-Move obj (vlax-3d-point ptw) (vlax-3d-point (scaleY ptw)))
		(vla-Update obj)
		(if (= kw "Y")
			(progn
				(setq scx (* (vla-get-XScaleFactor obj) scale))
				(setq scy (* (vla-get-YScaleFactor obj) scale))
				(setq scz (* (vla-get-ZScaleFactor obj) scale))
				(vla-put-XScaleFactor obj scx)
				(vla-put-YScaleFactor obj scy)
				(vla-put-ZScaleFactor obj scz)
			)
		)
		(vla-Update obj)
	)
	(defun mod-dimension (ename / data obj)
		(setq data (entget ename))
		(setq obj (vlax-ename->vla-object ename))
		(setq pt10w (cdr (assoc 10 data)))
		(setq pt11w (cdr (assoc 11 data)))
		(setq pt13w (cdr (assoc 13 data)))
		(setq pt14w (cdr (assoc 14 data)))
		(setq data (subst (cons 10 (scaleY pt10w)) (assoc 10 data) data))
		(setq data (subst (cons 11 (scaleY pt11w)) (assoc 11 data) data))
		(setq data (subst (cons 13 (scaleY pt13w)) (assoc 13 data) data))
		(setq data (subst (cons 14 (scaleY pt14w)) (assoc 14 data) data))
		(entmod data)
		(if (= kw "Y")
			(progn
				(vla-put-ScaleFactor obj (* (vla-get-ScaleFactor obj) scale))
			)
		)
		(vla-Update obj)
	)
	(defun scaleY (ptw / ptu)
		(setq ptu (trans ptw 0 1))
		(setq ptu (list (car ptu) (* (cadr ptu) Scale) (caddr ptu)))
		(trans ptu 1 0)
	)
	(defun *error*(s)
		(if ucsChanged (if command-s (command-s "_.ucs" "_p") (command "_.ucs" "_p")))
		(princ s)
		(vla-EndUndoMark doc)
		(princ)
	)
	(main)
)
