(defun c:hatchMove
	(/
		*error* main
		doc obj pt1 pt2 ename i  sa ucsChanged
	)
	(defun main()
		(vl-load-com)
		(setq doc (vla-get-ActiveDocument (vlax-get-acad-object)))
		(vla-StartUndoMark doc)
		(setvar "cmdecho" 0)
		(princ "\nhatchMove")
		(if (setq ss (ssget "_:L" '((0 . "HATCH"))))
			(progn
				(initget 1)
				(setq pt1 (getpoint "1点目を指定:"))
				(initget 1)
				(setq pt2 (getpoint pt1 "2点目を指定:"))
				(setq i 0)
				(setq pt1w (trans pt1 1 0))
				(setq pt2w (trans pt2 1 0))
				(setq mPt (mapcar '- pt2w pt1w))
				(command "_ucs" "w")
				(setq ucsChanged t)
				(repeat (sslength ss)
					(setq obj (vlax-ename->vla-object (setq ename (ssname ss i))))
					(setq orgPt (vlax-safearray->list (vlax-variant-value (vla-get-Origin obj))))
					(setq newPt (mapcar '+ orgPt mpt))
					(setq sa (vlax-make-safearray vlax-vbDouble '(0 . 1)))
					(setq sa (vlax-safearray-fill sa newPt))
					(setq pname (vla-get-PatternName obj))
					(cond
						((= pname "_USER")
							(vla-put-Origin obj sa)
							(command "_hatchedit"  ename "p" "u" "" "" "")
							(vla-Update obj)
						)
						((= pname "SOLID")
							;;(print "solid")
						)
						(t
							(vla-put-Origin obj sa)
							(command "_hatchedit"  ename "p" "" "" "")
							(vla-Update obj)
						)
					)
					(setq i (1+ i))
				)
				(command "_ucs" "p")
			)
		)
		(vla-EndUndoMark doc)
		(princ)
	)
	(defun *error*(s)
		(while (= (getvar "cmdactive") 1)  (command-s ""))
		(if ucsChanged (command-s "_ucs" "p"))
		(princ s)
		(vla-EndUndoMark doc)
		(princ)
	)
	(main)
)
