(defun c:textEditAd (/ *error* main doc)
	(vl-load-com)
	(defun main (/ res ename)
		(princ "\ntextEditAd")
		(vla-StartUndoMark (setq doc (vla-get-ActiveDocument (vlax-get-acad-object))))
		(setq ss (cadr (ssgetfirst)))
		(sssetfirst)
		(cond
			((and ss (= (sslength  ss) 1))
				(setq ename (ssname ss 0))
			)
			(t
				(if
					(and
						(setq pick (entsel))
						(= "TEXT" (cdr (assoc 0 (entget (car pick)))))
					)
					(progn
						(setq ename (car pick))
					)
				)
			)
		)
		(if ename
			(progn
				(setq res (editDlg (cdr (assoc 1 (entget ename)))))
				(print res)
				(if res
					(progn
						(setq data (subst (cons 1 res) (assoc 1 (entget ename)) (entget ename)))
						(entmod data)
					)
				)
			)
		)
		(vla-EndUndoMark doc)
		(princ)
	)
	(defun editDlg (orgstr / res ret newstr names strlst)
		(defun OnAccept_Clicked(e)
			(setq newstr (get_tile "userValue"))
			(done_dialog 1)
		)
		(defun OnCancel_Clicked(e)
			(done_dialog 0)
		)
		(defun OnListBox_Clicked(e)
			(set_tile "userValue" (nth (atoi e) names))
		)
		(defun readall (fn / dsc res lst)
			(setq dsc (open fn "r"))
			(while (setq res (read-line dsc))
				(setq lst (cons res lst))
			)
			(close dsc)
			(reverse lst)
		)
		(setq tempDcl (findfile "textEditAd.dcl"))
		(if (new_dialog "dlg" (setq id (load_dialog tempDcl)))
			(progn
				(setq txtfname (strcat (getvar "tempprefix") "textEditAd.txt"))
				(if (null (findfile txtfname))
					(progn
						(setq dsc (open txtfname "w"))
						(close dsc)
					)
				)
				(setq strlst (vl-remove-if '(lambda (a) (= a "")) (readall txtfname)))
				(setq names strlst)
				(start_list "listbox")
				(mapcar 'add_list  names)
				(end_list)
				(set_tile "listbox" "0")
				(set_tile "userValue" orgstr)
				(action_tile "accept" "(OnAccept_Clicked $value)")
				(action_tile "cancel" "(OnCancel_Clicked $value)")
				(action_tile "listbox" "(OnListbox_clicked $value)")
				(setq res (start_dialog))
				(unload_dialog id)
				(cond
					((= res 0)
						(setq ret nil)
					)
					((= res 1)
						(if (= newstr "") (setq newstr orgstr))
						(setq strlst (vl-remove newstr strlst))
						(setq strlst (cons newstr strlst))
						(setq dsc (open txtfname "w"))
						(foreach s strlst
							(write-line s dsc)
						)
						(close dsc)
						(setq ret newstr)
					)
				)
			)
		)
		ret
	)
	(defun *error*(s)
		(princ s)
		(vla-EndUndoMark doc)
		(princ)
	)
	(main)
)
