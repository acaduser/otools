(defun c:linkScale (/ *error* main doc)
	(vl-load-com)
	(defun main(/ i)
		(princ "\nlinkScale")
		(vla-StartUndoMark (setq doc (vla-get-ActiveDocument (vlax-get-acad-object))))
		(if (setq ss (ssget "_:L"))
			(progn
				(initget 1)
				(setq ptu (getpoint "\nbase:"))
				(setq ptw (trans ptu 1 0))
				(initget 7)
				(setq sc (getreal "\nscale:"))
				(command "_.scale" ss "" ptu sc)
				(setq i 0)
				(repeat (sslength ss)
					(setq ename (ssname ss i))
					(setq obj (vlax-ename->vla-object (ssname ss i)))
					(setq oname (cdr (assoc 0 (entget ename))))
					(if (wcmatch oname "*DIMENSION*")
						(progn
							(vla-put-ScaleFactor obj (* (vla-get-ScaleFactor obj) sc))
							(if (vlax-property-available-p obj 'LinearScaleFactor)
								(progn
									(vla-put-LinearScaleFactor obj (/ (vla-get-LinearScaleFactor obj) sc))
								)
							)
							(vla-Update obj)
						)
					)
					(setq i (1+ i))
				)
			)
		)
		(vla-EndUndoMark doc)
		(princ)
	)
	(defun *error*(s)(princ s)(vla-EndUndoMark doc)(princ))
	(main)
)
