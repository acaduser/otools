(defun c:batchPurge (/ *error* main doc)
	(vl-load-com)
	(defun main ( / fnames)
		(princ "\nbatchPurge")
		(if (setq fnames (getDWGFnames))
			(progn
				(textscr)
				(setq fnames (vl-sort fnames '<))
				(mapcar '(lambda (x) (princ (strcat "\n" x))) fnames)
				(princ (strcat "\n" (itoa (length fnames)) " dwg file found in clipboard."))
				(setq closeLst (check fnames))
				(if (null closeLst)
					(progn
						(setq scrName (writeScr fnames))
						;;(princ (strcat "\n" scrName))
						(getkword "\nPress enter. and start.")
						(command "script" scrName)
					)
					(progn
						(foreach fn closeLst
							(princ (strcat "\nClose please. " fn))  
						)
					)
				)
			)
			(progn
				(princ "\nNot found filepath in clipboard text.")
			)
		)
		(princ)
	)
	(defun writeScr (lst / scrName dsc )
		(setq scrName (strcat (getvar "tempprefix") "tmp.scr"))
		(setq dsc (open scrName "w"))
		(foreach fn lst
			(write-line "open" dsc)
			(write-line (strcat "\"" fn "\"") dsc)
			(write-line "zoom" dsc)
			(write-line "e" dsc)
			(write-line "purge" dsc)
			(write-line "a" dsc)
			(write-line "*" dsc)
			(write-line "n" dsc)
			(write-line "qsave" dsc)
			(write-line "close" dsc)
		)
		(close dsc)
		scrName	
	)
	(defun check (lst / fullname tmp)
		(vlax-for doc (vla-get-Documents (vlax-get-acad-object))
			(setq fullname (vla-get-FullName doc))
			(if (member fullname lst)
				(progn
					(setq tmp (cons fullname tmp))
				)
			)
		)
		tmp
	)
	(defun getDWGFnames( / obj ppp ccc cbText ret)
		(setq obj (vlax-create-object "htmlfile"))
		(setq ppp (vlax-get-property obj "parentwindow"))
		(setq ccc (vlax-get-property ppp "clipboarddata"))
		(if (setq cbText (vlax-invoke ccc 'getData "text" ))
			(progn
				(foreach str (split cbText "\r\n")
					(setq str (vl-string-left-trim "\"" str))
					(setq str (vl-string-right-trim "\"" str))
					(if (and (findfile str) (= (vl-filename-extension str) ".dwg"))
						(progn
							(setq ret (cons str ret))
						)
					)
				)
			)
		)
		ret
	)
	(defun split(str ptn / pos)
		(if (setq pos (vl-string-search ptn str))
			(cons (substr str 1	pos) (split (substr str (+ (1+ pos) (strlen ptn))) ptn))
			(list str)
		)
	)
	(defun *error*(s)
		(princ s)
		(princ)
	)
	(main)
)
