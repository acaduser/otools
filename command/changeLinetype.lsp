(defun c:changeLinetype (/ *error* main doc enames ss pick i)
	(vl-load-com)
	(defun main()
		(princ "\n✍changeLinetype")
		(vla-StartUndoMark (setq doc (vla-get-ActiveDocument (vlax-get-acad-object))))
		(if (setq ss (ssget "_:L"))
			(progn
				(setq i 0)
				(repeat (sslength ss) (setq enames (cons (ssname ss i) enames) i (1+ i)))
				(reverse enames)
				(mapcar '(lambda(x) (redraw x 3)) enames)
				(initget " ")
				(setq pick (entsel "\n参考にするオブジェクト選択<ダイアログ>:"))
				(cond
					((= (type pick) 'LIST)
						(setq data (entget (car pick)))
						(if (setq name (cdr (assoc 6 data)))
							(modifyName ss name)
							(modifyName ss "ByLayer")
						)
					)
					((= pick "") 
						(setq res (lineTypeDlg "ByLayer" t))
						(if res (modifyName ss res))
					)
					((null pick)
					)
				)
			)
		)
		(if enames (mapcar '(lambda(x) (redraw x 4)) enames))
		(vla-EndUndoMark doc)
		(princ)
	)
	(defun lineTypeDlg (lineType flag / names num id tbl res)
		(setq lineType (strcase lineType))
		(setq dsc (open (setq tempDcl (strcat  (getvar "tempprefix") "changeLinetype.dcl")) "w"))
		(write-line
"lineTypeDlg : dialog {
	label = \"✍線種選択\";
	: column {
		: list_box {
			height = 28;
			width = 40;
			key = \"listbox\";
			allow_accept = true;
		}
	ok_cancel;
	}
}"
			dsc
		)
		(close dsc)
		(if (new_dialog "lineTypeDlg" (setq id (load_dialog tempDcl)))
			(progn
				(action_tile "accept" "(done_dialog 1)")
				(action_tile "cancel" "(done_dialog 0)")
				(action_tile "listbox" "(setq num $value)")
				(if flag (setq names (list "ByLayer" "Byblock")))
				(while (if (null tbl) (setq tbl (tblnext "LTYPE" t)) (setq tbl (tblnext "LTYPE")))
					(setq name (cdr (assoc 2 tbl)))
					(if (wcmatch name "~*|*")
						(setq names (cons name names))
					)
				)
				(setq names (vl-sort names '<))
				(start_list "listbox")
				(mapcar 'add_list  names)
				(end_list)
				(if(vl-member-if '(lambda(x) (= (strcase lineType) (strcase x))) names)
					(setq num (itoa (vl-position lineType (mapcar 'strcase names))))
					(setq num (itoa (vl-position (strcase "Continuous")(mapcar 'strcase names))))
				)
				(set_tile "listbox" num)
				(setq res (start_dialog))
				(unload_dialog id)
			)
		)
		(if (/= res 0) (nth (atoi num) names))
	)
	(defun modifyName(ss e / )
		(command "_.chprop" ss "" "lt" e "")
		(princ (strcat "\n" e))
	)
	(defun *error*(s)
		(mapcar '(lambda(x) (redraw x 4)) enames)
		(princ s)
		(vla-EndUndoMark doc)
		(princ)
	)
	(main)
)
