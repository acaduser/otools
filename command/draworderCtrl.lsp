(defun c:draworderAuto (/ *error* main doc)
	(vl-load-com)
	(defun main()
		(princ "\ndraworderAuto")
		(vla-StartUndoMark (setq doc (vla-get-ActiveDocument (vlax-get-acad-object))))
		(setvar "cmdecho" 0)
		(sssetfirst)
		(draworder_b (list (cons 410 (getvar "ctab")) (cons 8 "color*")))
		(draworder_b (list (cons 410 (getvar "ctab")) (cons 8 "nuri*")))
		(draworder_b (list (cons 410 (getvar "ctab")) (cons 8 "nuri0*")))
		(draworder_f (list (cons 410 (getvar "ctab")) (cons 8 "mask*")))
		(draworder_f (list (cons 410 (getvar "ctab")) (cons 8 "moji*")))
		(vla-EndUndoMark doc)
		(princ)
	)
	(defun draworder_b (fi / )
		(if (setq ss (ssget "_X" fi)) (command "_draworder" ss "" "_b"))
		(print fi)
	)
	(defun draworder_f (fi / )
		(if (setq ss (ssget "_X" fi)) (command "_draworder" ss "" "_f"))
		(print fi)
	)
	(defun *error*(s)
		(princ s)
		(vla-EndUndoMark doc)
		(princ)
	)
	(main)
)
(defun c:draworderLayer () (c:draworderLayer_args nil))
(defun c:draworderLayer_args (kw / *error* main doc enames lnames)
	(vl-load-com)
	(defun main()
		(princ "\ndraworderLayer")
		(if kw (print kw))
		(vla-StartUndoMark (setq doc (vla-get-ActiveDocument (vlax-get-acad-object))))
		(if (setq ss (ssget))
			(progn
				(vl-load-com)
				(setq enames (ss->enames ss))
				(setq lnames (mapcar '(lambda (e) (cdr (assoc 8 (entget e)))) enames))
				(setq lnames (marge (vl-sort lnames '<)))
				(setq lst (apply 'append (mapcar '(lambda (a) (list a ",")) lnames)))
				(setq str (apply 'strcat (reverse (cdr (reverse lst)))))
				(if (and (= (vla-get-ActiveSpace doc) 0) (= (vla-get-MSpace doc) ':vlax-false))
					(setq filter (list (cons 8 str) (cons 410 (getvar "ctab"))))
					(setq filter (list (cons 8 str) (cons 410 "Model")))
				)
				(print filter)
				(terpri)
				(if (null kw)
					(progn
						(initget 7 "B F")
						(setq kw (getkword "\n[Back(B)/Front(F)]:"))
					)
				)
				(cond
					((= kw "B") (setq key "_b"))
					((= kw "F") (setq key "_f"))
					(t (setq key "_b"))
				)
				(setq ss (ssget "_X" filter))
				(setvar "cmdecho" 1)
				(command "_.draworder" ss "" key)
				(command "_.regen")
			)
		)
		(vla-EndUndoMark doc)
		(princ)
	)
	(defun ss->enames (ss / tmp i)
		(setq i 0)
		(repeat (sslength ss) (setq tmp (cons (ssname ss i) tmp) i (1+ i)))
		(reverse tmp)
	)
	(defun marge (lst / tmp)
		(mapcar '(lambda(a b) (if (/= a b) (setq tmp (cons a tmp)))) lst (cdr lst))
		(reverse (cons (last lst) tmp))
	)
	(defun *error*(s)
		(princ s)
		(vla-EndUndoMark doc)
		(princ)
	)
	(main)
)
