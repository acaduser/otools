(defun c:chBylayerTColor (/ *error* main doc ename name index)
	(vl-load-com)
	(defun main()
		(princ "\nchBylayerTColor")
		(vla-StartUndoMark (setq doc (vla-get-ActiveDocument (vlax-get-acad-object))))
		(if
			(and
				(setq ss (ssget))
				(setq res (acad_truecolordlg 7 nil))
			)
			(progn
				(setq enames (ss->enames ss))
				(setq layerList (vl-sort (mapcar '(lambda(x) (cdr(assoc 8 (entget x)))) enames) '<))
				(acet-layerp-mark t)
				(mapcar 'print res)
				(vlax-for oLayer (vla-get-Layers doc)
					;;(setq name (vla-get-name oLayer));;unicode NG
					(setq lname (cdr (assoc 2 (entget (vlax-vla-object->ename oLayer)))))

					(if (member lname layerList)
						(progn
							(setq tc (vla-get-TrueColor oLayer))
							(cond
								((setq color (cdr (assoc 430 res)))
									(setq lst (split color "$"))
									;;(print lst)
									(vla-SetNames tc (cadr lst) (car lst))
									(setq RGB (cdr (assoc 420 res)))
									(setq R (logand (lsh RGB -16) 255))
									(setq G (logand (lsh RGB -8) 255))
									(setq B (logand RGB 255))
									;;(print (list R G B))
									(vla-SetRGB tc R G B)
									(vla-put-TrueColor oLayer tc)
									
								)
								((setq RGB (cdr (assoc 420 res)))
									(vla-SetNames tc "" "")
									(setq R (logand (lsh RGB -16) 255))
									(setq G (logand (lsh RGB -8) 255))
									(setq B (logand RGB 255))
									;;(print (list R G B))
									(vla-SetRGB tc R G B)
									(vla-put-TrueColor oLayer tc)
								)
								((setq index (cdr (assoc 62 res)))
									(vla-SetNames tc "" "")
									;;(print lst)
									(vla-put-ColorIndex tc index)
									(vla-put-TrueColor oLayer tc)
								)
							)
						)
					)
				)
				(acet-layerp-mark nil)				
			)
		)
		(vla-EndUndoMark doc)
		(princ)
	)
	(defun split(str ptn / pos)
		(if (setq pos (vl-string-search ptn str))
			(append (list (substr str 1	pos)) (split (substr str (+ (1+ pos) (strlen ptn))) ptn))
			(list str)
		)
	)
	(defun ss->enames (ss / tmp i)
		(setq i 0)
		(repeat (sslength ss) (setq tmp (cons (ssname ss i) tmp) i (1+ i)))
		(reverse tmp)
	)
	(defun *error*(s)
		(princ s)
		(vla-EndUndoMark doc)
		(princ)
	)
	(apply 'main nil)
)
