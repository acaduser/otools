(defun c:angHatch
	(/
		*error* main
		doc obj pt1 pt2 ename i angw ucsChanged
	)
	(defun main()
		(vl-load-com)
		(setq doc (vla-get-ActiveDocument (vlax-get-acad-object)))
		(vla-StartUndoMark doc)
		(setvar "cmdecho" 0)
		(princ "\nangHatch")
		(if (setq ss (ssget "_:L" '((0 . "HATCH"))))
			(progn
				(initget 1)
				(setq pt1 (getpoint "\n1点目を指定:"))
				(initget 1)
				(setq pt2 (getpoint pt1 "\n2点目を指定:"))
				(setq i 0)
				(setq angw (angle (trans pt1 1 0) (trans pt2 1 0)))
				(command "_ucs" "w")
				(setq ucsChanged t)
				(repeat (sslength ss)
					(setq obj (vlax-ename->vla-object (setq ename (ssname ss i))))
					(setq pname (vla-get-PatternName obj))
					(cond
						((= pname "_USER")
							(command "_hatchedit"  ename "p" "u" "" "" "")
							(vla-put-PatternAngle obj angw)
							(vla-Update obj)
						)
						((= pname "SOLID")
							;;(print "solid")
						)
						(t
							(command "_hatchedit"  ename "p" "" "" "")
							;;(while (= (getvar "cmdactive") 1) (command ""))
							(vla-put-PatternAngle obj angw)
							(vla-Update obj)
						)
					)
					(setq i (1+ i))
				)
				(command "_ucs" "p")
			)
		)
		(vla-EndUndoMark doc)
		(princ)
	)
	(defun *error*(s)
		(while (= (getvar "cmdactive") 1) (command-s ""))
		(if ucsChanged (command-s "_ucs" "p"))
		(princ "\n😆")
		(princ s)
		(vla-EndUndoMark doc)
		(princ)
	)
	(main)
)
