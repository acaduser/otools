(defun c:stepMove
	(/
		*error* main ss->enames
		OnMouseClicked OnMouseMoved OnKeyPress add del
		doc ss ang pt1 pt2 objects loop baseSa pitch
		num newNum cmdecho saList
		UcsIsChanged ucsicon
	)
	(vl-load-com)
	(defun main()
		(princ "\nstepMove")
		(vla-StartUndoMark (setq doc (vla-get-ActiveDocument (vlax-get-acad-object))))
		(setq cmdecho (getvar "cmdecho"))
		(setvar "cmdecho" 0)
		(if (setq ss (ssget "_:L"))
			(progn
				(setq objects (reverse (mapcar 'vlax-ename->vla-object (ss->enames ss))))
				(initget 1)
				(setq pt1u (getpoint "\n基準点を指示:"))
				(setq loop t)
				(while loop
					(initget 1)
					(setq pt2u  (getpoint pt1u  "\n目的点を指示:"))
					(setq pitch (distance pt1u pt2u))
					(if (not (zerop pitch)) (setq loop nil))
				)
				(setq pt1 (trans pt1u 1 0))
				(setq pt2 (trans pt2u 1 0))
				(if (= (getvar "blockeditor") 0)
					(progn
						(command "_ucs" "_3p" "_non" pt1u "_non" pt2u "")
						(setq UcsIsChanged t)
					)
				)
				(setq ucsicon (getvar "ucsicon"))
				(setvar "ucsicon" 0)
				(setq ang (angle pt1 pt2))
				(setq baseSa
					(vlax-safearray-fill
						(vlax-make-safearray vlax-vbObject (cons 0 (1- (length objects)))) 
						objects
					)
				)
				(setq grloop t  num 0)
				(printMsg (strcat "\r@" (rtos pitch) "  " (rtos (* pitch num)) "(" (itoa num) ")"))
				(while grloop
					(setq gr (grread t 13 0))
					(cond
						((= (car gr) 2) (OnKeyPress gr))
						((= (car gr) 3) (OnMouseClicked gr))
						((= (car gr) 5) (OnMouseMoved gr))
					)
				)
				(redraw)
				(foreach o objects
					(vla-Highlight o ':vlax-false)
				)
			)
		)
		(if UcsIsChanged (command "_ucs" "_p" ))
		(if ucsicon (setvar "ucsicon" ucsicon))
		(setvar "cmdecho" cmdecho)
		(vla-EndUndoMark doc)
		(princ)
	)
	(defun printMsg(str)
		(repeat (- 50 (strlen str))
			(setq str (strcat str " "))
		)
		(princ str)
	)
	(defun OnMouseClicked(e)
		(setq grloop nil)
	)
	(defun OnKeyPress(e)
		(if (or (= (cadr e) 13) (= (cadr e) 32))
			(setq grloop nil)
		)
	)
	(defun OnMouseMoved(e / angdir sang)
		(setq optu (cadr e))
		(setq pt1u (trans pt1 0 1) pt2u (trans pt2 0 1))
		(redraw)
		(setq ptw (trans  (mapcar '- optu pt1u) 0 (mapcar '- pt2u pt1u)))
		(if (>= (caddr ptw) 0)
			(progn
				(setq newNum (fix(/ (caddr ptw) pitch)))
			)
			(progn
				(setq newNum (1- (fix(/ (* 1  (caddr ptw)) pitch))))
			)
		)
		(while (/= num newNum)
			(setq difNum (- newNum num))
			(move difNum)
			(setq num newNum)
			(printMsg (strcat "\r@" (rtos pitch) "  " (rtos (* pitch num)) "(" (itoa num) ")"))
		)
	)
	(defun move(pos / sa tmp mat)
		(setq movept (mapcar '(lambda(x) (* pos x)) (mapcar '- pt2 pt1)))
		(setq mat (vlax-tmatrix (MatrixMove movept)))
		(foreach o (vlax-safearray->list baseSa)
			(setq tmp
				(vl-catch-all-apply 'vla-TransformBy (list o  mat))
			)
		)
	)	
	(defun MatrixMove(v)
		(list
			(list 1.0 0.0 0.0 (car   v))
			(list 0.0 1.0 0.0 (cadr  v))
			(list 0.0 0.0 1.0 (caddr v))
			(list 0.0 0.0 0.0 1.0      )
		)
	)
	(defun ss->enames (ss / tmp i)
		(setq i 0)
		(repeat (sslength ss) (setq tmp (cons (ssname ss i) tmp) i (1+ i)))
		(reverse tmp)
	)
	(defun *error*(s)	
		(if UcsIsChanged (command-s "_ucs" "_p" ))
		(if ucsicon (setvar "ucsicon" ucsicon))
		(setvar "cmdecho" cmdecho)
		(princ (strcat "\n" s))
		(vla-EndUndoMark doc)
		(princ)
	)
	(main)
)
