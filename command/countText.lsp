(defun c:countText (/ *error* main doc)
	(vl-load-com)
	(defun main ()
		(princ "\ncountText")
		(setq htmlfile (vlax-create-object "htmlfile"))
		(setq ppp (vlax-get-property htmlfile "parentwindow"))
		(setq ccc (vlax-get-property ppp "clipboarddata"))
		(vla-StartUndoMark (setq doc (vla-get-ActiveDocument (vlax-get-acad-object))))
		(if (setq ss (ssget ":L" '((0 . "TEXT"))))
			(progn
				(setq i 0 tStrLst nil)
				(repeat (sslength ss)
					(setq ename (ssname ss i))
					(setq tStrLst (cons (cdr (assoc 1 (entget ename))) tStrLst))
					(setq i (1+ i))
				)
				(setq str "")
				(foreach tStr (vl-sort (unique tStrLst) '<)
					(setq lst (vl-remove-if-not '(lambda (x) (= tStr x)) tStrLst))
					(print (list tStr (length lst)))
					(setq str (strcat str "\n" tStr "\t" (itoa (length lst))))
				)
				(setq str (vl-string-left-trim "\n" str))
				;;(print str)
				(vlax-invoke ccc 'setData "text" str)
			)
		)
		(vla-EndUndoMark doc)
		(princ)
	)
	(defun unique (l)
		(if l (cons (car l) (unique (vl-remove (car l) l))))
	)
	(defun *error*(s)(princ s)(vla-EndUndoMark doc)(princ))
	(main)
)
