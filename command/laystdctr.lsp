(defun c:layAllOn(/ doc)
	(vl-load-com)
	(princ "\n💡")
	(vla-StartUndoMark (setq doc (vla-get-ActiveDocument (vlax-get-acad-object))))
	(acet-layerp-mark t)
	(vlax-for lay (vla-get-Layers doc)
		(vla-put-LayerOn lay ':vlax-true)
	)
	(acet-layerp-mark nil)
	(vla-EndUndoMark doc)
	(princ)
)
(defun c:layAllOff(/ doc)
	(vl-load-com)
	(vla-StartUndoMark (setq doc (vla-get-ActiveDocument (vlax-get-acad-object))))
	(acet-layerp-mark t)
	(vlax-for lay (vla-get-Layers doc)
		(if (= (cdr (assoc 2 (entget (vlax-vla-object->ename lay)))) (getvar "clayer"))
			(vla-put-LayerOn lay ':vlax-true)
			(vla-put-LayerOn lay ':vlax-false)
		)
	)
	(acet-layerp-mark nil)
	(vla-EndUndoMark doc)
	(princ)
)
(defun c:laySSON (/ *error* main doc)
	(vl-load-com)
	(defun main()
		(vla-StartUndoMark (setq doc (vla-get-ActiveDocument (vlax-get-acad-object))))
		(if (setq ss (ssget))
			(progn
				(setq enames (ss->enames ss))
				(setq names
					(unique (vl-sort (mapcar '(lambda(x) (cdr(assoc 8 (entget x)))) enames) '<))
				)
				(acet-layerp-mark t)
				(vlax-for lay (vla-get-Layers doc)
					(setq name (cdr (assoc 2 (entget (vlax-vla-object->ename lay)))))
					(if (not (member name names))
						(vla-put-LayerOn lay ':vlax-false)
					)
				)
				(acet-layerp-mark nil)
				(if (< (cdr (assoc 62 (entget (tblobjname "layer" (getvar "clayer"))))) 0)
					(progn
						(setvar "clayer" (car names))
						(princ (strcat "\n現在の画層は " (car names) " に設定されました。"))
					)
				)
			)
		)
		(vla-EndUndoMark doc)
		(princ)
	)
	(defun ss->enames (ss / tmp i)
		(setq i 0)
		(repeat (sslength ss) (setq tmp (cons (ssname ss i) tmp) i (1+ i)))
		(reverse tmp)
	)
	(defun unique(lst / tmp)
		(mapcar '(lambda(a b) (if (/= a b) (setq tmp (cons a tmp)))) lst (cdr lst))
		(reverse (cons (last lst) tmp))
	)
	(defun *error* (s)
		(princ s)
		(vla-EndUndoMark doc)
		(princ)
	)
	(main)
)
(defun c:laySSOff (/ *error* main doc)
	(vl-load-com)
	(defun main()
		(vla-StartUndoMark (setq doc (vla-get-ActiveDocument (vlax-get-acad-object))))
		(if (setq ss (ssget))
			(progn
				(setq enames (ss->enames ss))
				(setq names
					(unique (vl-sort (mapcar '(lambda(x) (cdr(assoc 8 (entget x)))) enames) '<))
				)
				(acet-layerp-mark t)
				(vlax-for lay (vla-get-Layers doc)
					(setq name (cdr (assoc 2 (entget (vlax-vla-object->ename lay)))))
					(if (member name names)
						(vla-put-LayerOn lay ':vlax-false)
					)
				)
				(acet-layerp-mark nil)
			)
		)
		(vla-EndUndoMark doc)
		(princ)
	)
	(defun ss->enames (ss / tmp i)
		(setq i 0)
		(repeat (sslength ss) (setq tmp (cons (ssname ss i) tmp) i (1+ i)))
		(reverse tmp)
	)
	(defun unique(lst / tmp)
		(mapcar '(lambda(a b) (if (/= a b) (setq tmp (cons a tmp)))) lst (cdr lst))
		(reverse (cons (last lst) tmp))
	)
	(defun *error* (s)
		(princ s)
		(vla-EndUndoMark doc)
		(princ)
	)
	(main)
)
(defun c:layPickNestOn (/ *error* main doc)
	(vl-load-com)
	(defun main ()
		(vla-StartUndoMark (setq doc (vla-get-ActiveDocument (vlax-get-acad-object))))
		(sssetfirst)
		(if (setq pick (nentsel "\nオブジェクト選択:"))
			(progn
				(setq enameList (last pick))
				(setq obj (vlax-ename->vla-object (car pick)))
				(setq name (cdr (assoc 8 (entget (car pick)))))
				(if (and (= name "0") (= (vla-get-ObjectName obj) "AcDbAttribute"))
					(setq name (cdr (assoc 8 (entget (vlax-vla-object->ename (vla-ObjectIDToObject doc (vla-get-OwnerID obj)))))))
				)
				(if (and (= name "0") (= (type (car enameList)) 'ENAME))
					(progn
						(setq bname
							(car
								(vl-remove-if
									'(lambda(x)
										(= (cdr (assoc 8 (entget x))) "0")
									)
									enameList
								)
							)
						)
						(if bname
							(setq name (cdr (assoc 8 (entget bname))))
							(setq name "0")
						)
					)
				)
				(acet-layerp-mark t)
				(vlax-for lay (vla-get-Layers doc)
					(if (= (cdr (assoc 2 (entget (vlax-vla-object->ename lay)))) name)
						(vla-put-LayerOn lay ':vlax-true)
						(vla-put-LayerOn lay ':vlax-false)
					)
				)
				(acet-layerp-mark nil)
				(print name)
			)
		)
		(vla-EndUndoMark doc)
		(princ)
	)
	(defun *error*(s)
		(princ s)
		(vla-EndUndoMark doc)
		(princ)
	)
	(main)
)
(defun c:layPickNestOff (/ *error* main doc)
	(vl-load-com)
	(defun main ()
		(vla-StartUndoMark (setq doc (vla-get-ActiveDocument (vlax-get-acad-object))))
		(sssetfirst)
		(if (setq pick (nentsel "\nオブジェクト選択:"))
			(progn
				(setq enameList (last pick))
				(setq obj (vlax-ename->vla-object (car pick)))
				(setq name (cdr (assoc 8 (entget (car pick)))))
				(if (and (= name "0") (= (vla-get-ObjectName obj) "AcDbAttribute"))
					(setq name (cdr (assoc 8 (entget (vlax-vla-object->ename (vla-ObjectIDToObject doc (vla-get-OwnerID obj)))))))
				)
				(if (and (= name "0") (= (type (car enameList)) 'ENAME))
					(progn
						(setq bname
							(car
								(vl-remove-if
									'(lambda(x)
										(= (cdr (assoc 8 (entget x))) "0")
									)
									enameList
								)
							)
						)
						(if bname
							(setq name (cdr (assoc 8 (entget bname))))
							(setq name "0")
						)
					)
				)
				(acet-layerp-mark t)
				(vlax-for lay (vla-get-Layers doc)
					(if (= (cdr (assoc 2 (entget (vlax-vla-object->ename lay)))) name)
						(vla-put-LayerOn lay ':vlax-false)
					)
				)
				(acet-layerp-mark nil)
				(print name)
			)
		)
		(vla-EndUndoMark doc)
		(princ)
	)
	(defun *error*(s)
		(princ s)
		(vla-EndUndoMark doc)
		(princ)
	)
	(main)
)
