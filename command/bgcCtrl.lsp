(defun c:bgcCtrl (/ *error* c)
	(defun main()
		(vl-load-com)
		(setq tilemode (getvar "tilemode"))
		(if (= tilemode 1)
			(setq sn "Model")
			(setq sn "Layout")
		)
		(princ (strcat "\n"  sn  " の背景色を調整"))
		(while (null c)
			(initget "B D L W")
			(setq res (getint "\n階調度を指定(0-255)[黒(B)/濃い灰(D)/淡い灰(L)/白(W)]<黒>:"))
			(if (null res) (setq c 0))
			(cond
				((null res) (setq c 0))
				((= res "B") (setq c 0))
				((= res "D") (setq c 85))
				((= res "L") (setq c 170))
				((= res "W") (setq c 255))
				((and (>= res 0) (<= res 255)) (setq c res))
				(t (princ "\n0-255"))
			)
		)
		(if (= tilemode 1)
			(c:bgcCtrl_Model c)
			(c:bgcCtrl_Layout c)
		)
		(print c)
		(princ)
	)
	(defun *error* (s)
		(princ s)
		(princ)
	)
	(main)
)
(defun c:bgcCtrl_Model (c / )
	(setq disp (vla-get-Display (vla-get-Preferences (vlax-get-acad-object))))
	(setq rgb (+ (lsh c 16) (lsh c 8) c))
	(vla-put-GraphicsWinModelBackgrndColor disp rgb)
	(if (<= c 128)
		(vla-put-ModelCrosshairColor disp (- (expt 2 24) 1))
		(vla-put-ModelCrosshairColor disp 0)
	)
	(princ)
)
(defun c:bgcCtrl_Layout (c / )
	(setq disp (vla-get-Display (vla-get-Preferences (vlax-get-acad-object))))
	(setq rgb (+ (lsh c 16) (lsh c 8) c))
	(vla-put-GraphicsWinLayoutBackgrndColor disp rgb)
	(if (<= c 128)
		(vla-put-LayoutCrosshairColor disp (- (expt 2 24) 1))
		(vla-put-LayoutCrosshairColor disp 0)
	)
	(princ)
)
