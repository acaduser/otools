(defun c:easySlice (/ *error* main doc)
	(vl-load-com)
	(defun main ()
		(princ "\n🔪easySlice")
		(vla-StartUndoMark (setq doc (vla-get-ActiveDocument (vlax-get-acad-object))))
		(setq spc (getspace doc))
		(if (setq ss (ssget "_:L" '((0 . "LINE,LWPOLYLINE,ARC,RAY,XLINE"))))
			(progn
				(setq pt1 (getpoint "\n1点目指定:"))
				(setq pt2 (getpoint pt1 "\n2点目指定:"))
				(setq pt1w (trans pt1 1 0) pt2w (trans pt2 1 0))
				(setq oLine (vla-AddLine spc (vlax-3d-point pt1w) (vlax-3d-point pt2w)))
				(setq i 0)
				(repeat (sslength ss)
					(setq ename (ssname ss i))
					(setq obj (vlax-ename->vla-object ename))
					(setq res (vla-IntersectWith obj oLine acExtendNone))
					(setq sa (vlax-variant-value res))
					(setq ub (vlax-safearray-get-u-bound sa 1))
					(if (>= ub 2)
						(progn
							(setq coords (vlax-safearray->list sa))
							(foreach n (coords->3DPtList coords)
								(command "_.break" "_non" (list ename (trans n 0 1))  "_non" (trans n 0 1))
							)
						)
					)
					(setq i (1+ i))
				)
				(vla-Delete oLine)
			)
		)
		(vla-EndUndoMark doc)
		(princ)
	)
	(defun coords->3DPtList (lst)
		(if lst (cons (list (car lst) (cadr lst) (caddr lst)) (coords->3DPtList (cdddr lst))))
	)
	(defun getspace(d)
		(if (and(= (vla-get-ActiveSpace d) 0)(= (vla-get-MSpace d) ':vlax-false))
			(vla-get-PaperSpace d)
			(vla-get-ModelSpace d)
		)
	)
	(defun *error*(s)
		(princ s)
		(vla-EndUndoMark doc)
		(princ)
	)
	(main)
)
