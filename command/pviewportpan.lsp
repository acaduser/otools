(defun c:pviewportpan
	(/
		;function
		program *error* 
		getactivespace userinput
		;private
		acapp acdoc acspace acutl aclayt acmspace acmlayout zeropt
		pname bname ss movedcount
	)
	(defun program(/)
		(terpri)
		(princ (strcat"\nビューポート表示範囲移動"))
		(vl-load-com)
		(setvar "cmdecho" 0)
		(setq acapp (vlax-get-acad-object))
		(setq acdoc (vla-get-activedocument acapp))
		(setq acpspace(vla-get-paperspace acdoc))
		(setq acutl (vla-get-utility acdoc))
		(setq aclayt (vla-get-activelayout acdoc))
		(setq acmspace (vla-get-modelspace acdoc))
		(setq acmlayout (vla-get-layout acmspace))
		(setq zeropt (vlax-3d-point '(0 0 0)))
		(setq movedcount 0)
		(if (= (getvar "tilemode") 0)
			(progn
				(if (= (vla-get-mspace acdoc) ':vlax-true) (vla-put-mspace acdoc ':vlax-false))
				(setq ss (ssget(list(cons 0 "VIEWPORT"))))
				(terpri)
				(if ss
					(progn
						(command "undo" "be")
						(userinput)
						(princ (strcat (itoa movedcount) "個のビューポート表示範囲は移動されました\n"))
					)
				)
			)
			(princ "\nモデル空間では使用できません")
		)
		
		(command "undo" "e")
		(princ)
	)
	(defun userinput(/ i )
		(initget 7)
		(setq pt1 (getpoint "基点指示:"))
		(terpri)
		(initget 39)
		(setq pt2 (getpoint pt1 "移動先指示:"))
		(terpri)
		(setq oldlocklist (pviewalllock))
		(setq i 0)
		(while (< i (sslength ss))
			(setq acpview (vlax-ename->vla-object (ssname ss i)))
			(setq subpt (mapcar '(lambda(x y) (*(- y x)-1)) pt1 pt2))
			(vla-display acpview ':vlax-true)
			(setq objectid (vla-get-objectid acpview))
			(if (= (vla-get-clipped acpview) ':vlax-true)
				(modifyrecvp)
				(modifyrecvp)
			)
			(setq i (1+ i))
		)
		(pviewalllockrecov oldlocklist)
	)
	(defun pviewalllock(/ acblock alloldlock)
		(setq acblock (vla-get-block aclayt))
		(vlax-for item acblock
			(if (= (vla-get-objectname item) "AcDbViewport")
				(progn
					(setq alloldlock
						(append	alloldlock
							(list (vla-get-displaylocked item))
						)
					)
					(vla-put-displaylocked item ':vlax-true)
				)
			)
		)
		alloldlock
	)
	(defun pviewalllockrecov(alloldlock / acblock i cnt)
		(setq acblock (vla-get-block aclayt))
		(setq i 0 cnt 0)
		(vlax-for item acblock
			(if (= (vla-get-objectname item) "AcDbViewport")
				(progn
					(vla-put-displaylocked item (nth cnt alloldlock))
					(setq cnt (1+ cnt))
				)
			)
			(setq i (1+ i))
		)		
	)
	(defun modifyrecvp(/ oldlocklist errobj111 errobj2111)
		(if (= (vla-get-mspace acdoc) ':vlax-false)
			(vl-catch-all-apply 'vla-put-mspace (list acdoc ':vlax-true))
		)
		(if (= (vla-get-mspace acdoc) ':vlax-true)
			(progn
				(vl-catch-all-apply 'vla-put-activepviewport (list acdoc acpview))
				(setq newacpview (vla-get-activepviewport acdoc))
				(if (= (vla-get-objectid newacpview) (vla-get-objectid acpview))
					(progn
						(setq customscale (vla-get-customscale acpview))
						(setq olducsfollow  (vla-getvariable acdoc "ucsfollow"))
						(vla-setvariable acdoc "ucsfollow" 0)
						(vla-put-displaylocked acpview ':vlax-false)
						(setq twist (vla-get-twistangle acpview))
						(setq ang (angle pt1 pt2))
						(setq dist (distance pt1 pt2))
						(setq newpt2 (polar pt1 (- ang twist) dist))
						(setq panpt1 (mapcar '(lambda(a)(/ a customscale)) pt1))
						(setq panpt2 (mapcar '(lambda(a)(/ a customscale)) newpt2))
						(command "-pan" "non" (trans panpt1 0 1) "non" (trans panpt2 0 1))
						(vla-setvariable acdoc "ucsfollow" olducsfollow)
						(setq movedcount (1+ movedcount))
			 		)
			 		(progn
			 		 	(vla-put-mspace acdoc ':vlax-false)
 						(princ "\nアクティブビューポートに割り当てれません")
			 		)
			 	)
			)
		)
		(if (>= i (- (sslength ss) 1))
			(progn
				(command "pspace")
			)
		)
	)
	(defun *error*(s)	
		(princ (strcat "\n" s))
		(vla-EndUndoMark acdoc)
		(princ)
	)
	(apply 'program nil)
)
