(defun c:pviewporttomodel
	(/
		main *error*  
		doc aclayt acmspace zeropt
		ss movedcount
	)
	(defun main(/)
		(vl-load-com)
		(princ "\nビューポート境界をモデル空間に作図")
		(setvar "cmdecho" 0)
		(setq doc (vla-get-ActiveDocument (vlax-get-acad-object)))
		(vla-StartUndoMark doc)
		(setq acmspace (vla-get-ModelSpace doc))
		(setq zeropt (vlax-3d-point '(0 0 0)))
		(setq movedcount 0)
		(if (= (getvar "tilemode") 0)
			(progn
				(if (= (vla-get-MSpace doc) ':vlax-true) (vla-put-MSpace doc ':vlax-false))
				(if (setq ss (ssget (list (cons 0 "VIEWPORT"))))
					(progn
						(setq i 0)
						(while (< i (sslength ss))
							(setq ename (ssname ss i))
							(setq acpview (vlax-ename->vla-object ename))
							(vla-Display acpview ':vlax-true)
							(if (setq linkename (cdr (assoc 340 (entget ename))))
								(modifyclipvp linkename)
								(modifyrecvp acpview)
							)
							(if (>= i (- (sslength ss) 1))
								(progn
									(command "pspace")
								)
							)
							(setq i (1+ i))
						)
						(princ (strcat (itoa movedcount) "個のビューポートをモデル空間に作図しました\n"))
					)
				)
			)
			(princ "\nモデル空間では使用できません")
		)
		(vla-EndUndoMark doc)
		(princ)
	)
	(defun modifyrecvp(acpview / ptlist sa coords acpline)
		(if (= (vla-get-mspace doc) ':vlax-false)
			(vl-catch-all-apply 'vla-put-mspace (list doc ':vlax-true))
		)
		(if (= (vla-get-MSpace doc) ':vlax-true)
			(progn
				(vl-catch-all-apply 'vla-put-activepviewport (list doc acpview))
				(setq newacpview (vla-get-ActivePViewport doc))
				(if (= (vla-get-ObjectID newacpview) (vla-get-ObjectID acpview))
					(progn
						(setq customscale (vla-get-CustomScale acpview))
						(setq twist (vla-get-TwistAngle acpview))
						(setq movedcount (1+ movedcount))
						(setq viewcenter (trans (getvar "viewctr") 1 0))
						(vla-GetBoundingBox acpview 'minpt 'maxpt )
						(setq
							listmin (vlax-safearray->list minpt)
							listmax (vlax-safearray->list maxpt)
						)
						(setq listcenpt (mapcar '(lambda(a b) (/ (+ a b) 2.0)) listmin listmax))
						(setq listbasemin (mapcar '(lambda (a b) (/ (- b a))) listcenpt listmin ))
						(setq listbasemax (mapcar '(lambda (a b) (/ (- b a))) listcenpt listmax ))
						
						(setq ptlist
							(append ptlist
								(list (car listbasemin) (cadr listbasemin))
								(list (car listbasemax) (cadr listbasemin))
								(list (car listbasemax) (cadr listbasemax))
								(list (car listbasemin) (cadr listbasemax))
							)
						)
						(setq sa (vlax-make-safearray vlax-vbdouble '(0 . 7)))
						(setq coords (vlax-safearray-fill sa ptlist))
						(setq acpline(vla-AddLightWeightPolyline acmspace coords))
						(vla-put-Closed acpline ':vlax-true)
						(vla-ScaleEntity acpline zeropt (/ 1 customscale))
						(vla-Rotate acpline zeropt (* -1 twist))
						(vla-Move acpline zeropt (vlax-3d-point viewcenter))
						(vla-Update acpline)
			 		)
			 		(progn
			 		 	(vla-put-MSpace doc ':vlax-false)
 						(princ "\nアクティブビューポートに割り当てれません")
			 		)
			 	)
			)
		)
	)
	(defun modifyclipvp(linkename / i ptlist sa coords acpline)
		(setq linkacpline (vlax-ename->vla-object linkename))
		(setq coords (vla-get-Coordinates linkacpline))
		(if (= (vla-get-MSpace doc) ':vlax-false)
			(vl-catch-all-apply 'vla-put-mspace (list doc ':vlax-true))
		)
		(if (= (vla-get-MSpace doc) ':vlax-true)
			(progn
				(vl-catch-all-apply 'vla-put-activepviewport (list doc acpview))
				(setq newacpview (vla-get-ActivePViewport doc))
				(if (= (vla-get-ObjectID newacpview) (vla-get-ObjectID acpview))
					(progn
						(setq customscale (vla-get-CustomScale acpview))
						(setq twist (vla-get-TwistAngle acpview))
						(setq movedcount (1+ movedcount))
						(setq viewcenter (trans (getvar "viewctr") 1 0))
						(vla-GetBoundingBox acpview 'minpt 'maxpt)
						(setq
							listmin (vlax-safearray->list minpt)
							listmax (vlax-safearray->list maxpt)
						)
						(setq listcenpt (mapcar '(lambda(a b) (/ (+ a b) 2.0)) listmin listmax))
						(setq ptlist (vlax-safearray->list (vlax-variant-value coords)))
						(setq ptlen (/ (length ptlist) 2))
						(setq acpline(vla-AddLightWeightPolyline acmspace coords))
						(vla-Move acpline (vlax-3d-point listcenpt) zeropt)
						(setq i 0)
						(repeat ptlen
							(vla-SetBulge acpline i (vla-GetBulge linkacpline i))
							(setq i (1+ i))
						)
						(vla-Update acpline)
						(vla-put-Closed acpline ':vlax-true)
						(vla-ScaleEntity acpline zeropt (/ 1 customscale))
						(vla-Rotate acpline zeropt (* -1 twist))
						(vla-Move acpline zeropt (vlax-3d-point viewcenter))
						(vla-Update acpline)
			 		)
			 		(progn
			 		 	(vla-put-MSpace doc ':vlax-false)
 						(princ "\nアクティブビューポートに割り当てれません")
			 		)
			 	)
			)
		)
	)
	(defun *error*(s)
		(vla-EndUndoMark doc)
		(princ s)
		(princ)
	)
	(apply 'main nil)
)
