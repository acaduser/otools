(defun c:srtobj
	(/
		main *error* 
		obj xy
	)
	(defun main()
		(vl-load-com)
		(princ "\nオブジェクトを線に垂直に移動する \n")
		
		(setq acApp (vlax-get-acad-object))
		(setq acDoc (vla-get-activedocument acApp))
		(vla-StartUndoMark acDoc)
		(if(setq ss (ssget "_:L"))
			(progn
				(initget 7)
				(setq pt1 (getpoint "\n1点目指示:"))
				(initget 39)
				(setq pt2 (trans (getpoint pt1 "\n2点目指示:") 1 0))
				(setq pt1 (trans pt1 1 0))
				(setq pt1 (xy0 pt1) pt2 (xy0 pt2))
				(setq ang (angle pt1 pt2))
				
				(setq i 0)
				(while (< i (sslength ss))
					(setq ename (ssname ss i))
					(setq obj (vlax-ename->vla-object ename))
					(setq oName (vla-get-ObjectName obj))
					(cond
						((= oname "AcDbArc")				(fromCenter))
						((= oname "AcDbCircle")				(fromCenter))
						((= oname "AcDbEllipse")			(fromCenter))
						((= oname "AcDbText")				(fromTextInsPoint))
						((= oname "AcDbAttributeDefinition")(fromTextInsPoint))
						((= oname "AcDbLine")				(fromMiddlePoint))
						((= oname "AcDbMText")				(fromInsPoint))
						((= oname "AcDbBlockReference")		(fromInsPoint))
						((= oname "AcDbTable")				(fromInsPoint))
						((= oname "AcDbPolyline")			(fromCoodinates2D))
						((= oname "AcDb2dPolyline")			(fromCoodinates3D))
						((= oname "AcDbFace")				(fromCoodinates3D))
						((= oname "AcDbMline")				(fromCoodinates3D))
						((= oname "AcDbPoint")				(fromCoodinates3D))
						((= oname "AcDbSolid")				(fromCoodinates3D))
						((= oname "AcDbTrace")				(fromCoodinates3D))
						((= oname "AcDb3dPolyline")			(fromCoodinates3D))
						((= oname "AcDbPolygonMesh")		(fromCoodinates3D))
						((= oname "AcDbRotatedDimension")	(fromDistPoint))
						((= oname "AcDbAlignedDimension")	(fromDistPoint))
						((= oname "AcDbRadialDimension")	(fromDxf10))
						((= oname "AcDbDiametricDimension")	(fromDxf10_15))
						((= oname "AcDb3PointAngularDimension")	(fromDxf15))
						((= oname "AcDbLeader")	(fromDxf10))
						
						
						(t nil)
					)
					(setq i (1+ i))
				)
			)
		)
		(vla-EndUndoMark acDoc)
		(vlax-release-object acapp)
		(princ)
	)
	
	(defun fromTextInsPoint(/ basePt align pt)
		
		(setq align (vla-get-alignment obj))
		(if (or (= align acAlignmentLeft) (= align acAlignmentAligned) (= align acAlignmentFit))
			(setq basePt (vla-get-insertionPoint obj))
			(setq basePt(vla-get-textAlignmentPoint obj))
		)
		(setq pt (vlax-safearray->list (vlax-variant-value basePt)))
		(setq pt (xy0 pt))

		(setq ptPolar (polar pt (+ ang (/ pi 2)) 1.0))
		(setq ptInters (inters pt1 pt2 pt ptPolar nil))
		;;(entmake (list (cons 0 "CIRCLE")(cons 40 0.5)(cons 10 ptInters)))
		(vla-move obj (vlax-3d-point  pt) (vlax-3d-point ptInters))
	)
	(defun fromCenter(/ )
		(setq pt (vlax-safearray->list (vlax-variant-value (vla-get-Center obj))))
		(setq pt (xy0 pt))
		(setq ptPolar (polar pt (+ ang (/ pi 2)) 1.0))
		(setq ptInters (inters pt1 pt2 pt ptPolar nil))
		(vla-move obj (vlax-3d-point  pt) (vlax-3d-point ptInters))
	)
	(defun fromInsPoint(/ )
		(setq pt (vlax-safearray->list (vlax-variant-value (vla-get-InsertionPoint obj))))
		(setq pt (xy0 pt))
		(setq ptPolar (polar pt (+ ang (/ pi 2)) 1.0))
		(setq ptInters (inters pt1 pt2 pt ptPolar nil))
		(vla-move obj (vlax-3d-point  pt) (vlax-3d-point ptInters))
	)
	(defun fromMiddlePoint(/ )
		(setq staPt (vlax-safearray->list (vlax-variant-value (vla-get-StartPoint obj))))
		(setq endPt (vlax-safearray->list (vlax-variant-value (vla-get-EndPoint obj))))
		(setq pt (mapcar '(lambda(a b) (/ (+ a b) 2.0)) staPt endPt))
		(setq pt (xy0 pt))
		(setq ptPolar (polar pt (+ ang (/ pi 2)) 1.0))
		(setq ptInters (inters pt1 pt2 pt ptPolar nil))
		(vla-move obj (vlax-3d-point  pt) (vlax-3d-point ptInters))
	)
	(defun fromCoodinates2D(/ pt ptList i)
		(setq coords (vlax-variant-value (vla-get-coordinates obj)))
		(setq coords (vlax-safearray->list coords))
		(setq i 0)
		(while (< i (length coords))
			(setq ptlist
				(append ptlist
					(list
						(list
							(nth i coords)
							(nth (+ i 1) coords)
							0
						)
					)
				)
			)
			(setq i (+ i 2))
		)
		(setq rotatedList
			(mapcar
				'(lambda(x)
					(polar '(0 0) (- (angle '(0 0) x) ang) (distance '(0 0) x))
				)
				ptlist
			)
		)
		(setq xList (mapcar 'car rotatedList))
		(setq yList (mapcar 'cadr rotatedList))
		(setq midPt
			(mapcar
				'(lambda(a b)
					(/ (+ a b) 2.0)
				)
				(list (apply 'min xList) (apply 'min yList))
				(list (apply 'max xList) (apply 'max yList))
			)
		)
		(setq pt (polar '(0 0) (+ (angle '(0 0) midPt) ang) (distance '(0 0) midPt)))
		;;(entmake (list (cons 0 "CIRCLE")(cons 40 0.5)(cons 10 midPt)))
		(setq ptPolar (polar pt (+ ang (/ pi 2)) 1.0))
		(setq ptInters (inters pt1 pt2 pt ptPolar nil))
		(vla-move obj (vlax-3d-point  pt) (vlax-3d-point ptInters))
	)
	(defun fromCoodinates3D(/ pt ptList i)
		(setq coords (vlax-variant-value (vla-get-coordinates obj)))
		(setq coords (vlax-safearray->list coords))
		(setq i 0)
		(while (< i (length coords))
			(setq ptlist
				(append ptlist
					(list
						(list
							(nth i coords)
							(nth (+ i 1) coords)
							0
						)
					)
				)
			)
			(setq i (+ i 3))
		)
		(setq rotatedList
			(mapcar
				'(lambda(x)
					(polar '(0 0) (- (angle '(0 0) x) ang) (distance '(0 0) x))
				)
				ptlist
			)
		)
		(setq xList (mapcar 'car rotatedList))
		(setq yList (mapcar 'cadr rotatedList))
		(setq midPt
			(mapcar
				'(lambda(a b)
					(/ (+ a b) 2.0)
				)
				(list (apply 'min xList) (apply 'min yList))
				(list (apply 'max xList) (apply 'max yList))
			)
		)
		(setq pt (polar '(0 0) (+ (angle '(0 0) midPt) ang) (distance '(0 0) midPt)))
		;;(entmake (list (cons 0 "CIRCLE")(cons 40 0.5)(cons 10 midPt)))
		(setq ptPolar (polar pt (+ ang (/ pi 2)) 1.0))
		(setq ptInters (inters pt1 pt2 pt ptPolar nil))
		(vla-move obj (vlax-3d-point  pt) (vlax-3d-point ptInters))
	)
	(defun fromDistPoint(/ )
		(setq pt (cdr (assoc 13 (entget ename))))
		(setq pt (xy0 pt))
		(setq ptPolar (polar pt (+ ang (/ pi 2)) 1.0))
		(setq ptInters (inters pt1 pt2 pt ptPolar nil))
		(vla-move obj (vlax-3d-point  pt) (vlax-3d-point ptInters))
	)
	(defun fromDxf10(/ pt)
		(setq pt (cdr (assoc 10 (entget ename))))
		(setq pt (xy0 pt))
		(setq ptPolar (polar pt (+ ang (/ pi 2)) 1.0))
		(setq ptInters (inters pt1 pt2 pt ptPolar nil))
		(vla-move obj (vlax-3d-point  pt) (vlax-3d-point ptInters))
	)
	(defun fromDxf10_15(/ pt)
		(setq pt
			(mapcar
				'(lambda(a b)
					(/ (+ a b) 2.0)
				)
				(cdr (assoc 10 (entget ename)))
				(cdr (assoc 15 (entget ename)))
			)
		)
		(setq pt (xy0 pt))
		(setq ptPolar (polar pt (+ ang (/ pi 2)) 1.0))
		(setq ptInters (inters pt1 pt2 pt ptPolar nil))
		(vla-move obj (vlax-3d-point  pt) (vlax-3d-point ptInters))
	)
	(defun fromDxf15(/ pt)
		(setq pt (cdr (assoc 15 (entget ename))))
		(setq pt (xy0 pt))
		(setq ptPolar (polar pt (+ ang (/ pi 2)) 1.0))
		(setq ptInters (inters pt1 pt2 pt ptPolar nil))
		(vla-move obj (vlax-3d-point  pt) (vlax-3d-point ptInters))
	)

	(defun xy0(pt)
		(list (car pt)(cadr pt) 0)
	)
	(defun *error* (s)(princ s)(vla-EndUndoMark acDoc)(princ))

	(main)
	
)
