(defun c:changeLayer
	(/
		*error* main doc
	)
	(defun main ()
		(vl-load-com)
		(princ "\n🌈changeLayer")
		(vla-StartUndoMark (setq doc (vla-get-ActiveDocument (vlax-get-acad-object))))
		(if (setq ss (ssget "_:L"))
			(progn
				(initget " ")
				(setq res (entsel "\n参考にするオブジェクト選択<ダイアログ>:"))
				(cond
					((= res "")
						(setq res (layerDlg "0" t))
						(if res (modifyName ss res))
					)
					((= (type res) 'LIST)
						(modifyName ss (cdr(assoc 8 (entget (car res)))))
					)
				)
			)
		)
		(vla-EndUndoMark doc)
		(princ)
	)
	(defun layerDlg(name flag / names num id tbl res)
		(setq name (strcase name))
		(setq tempDcl (findfile "changelayer.dcl"))
		(if (new_dialog "lineTypeDlg" (setq id (utf8load_dialog tempDcl)))
			(progn
				(action_tile "accept" "(OnAccept_Clicked $value)")
				(action_tile "cancel" "(OnCancel_Clicked $value)")
				(action_tile "userInput" "(OnUserInput_clicked $value)")
				(action_tile "userValue" "")
				(action_tile "listbox" "(OnListbox_clicked $value)")
				(while (if (null tbl) (setq tbl (tblnext "LAYER" t)) (setq tbl (tblnext "LAYER")))
					(setq lname (cdr (assoc 2 tbl)))
					(if (wcmatch lname "~*|*")
						(setq names (cons lname names))
					)
				)
				(setq names (vl-sort names '(lambda(a b)(< (strcase a) (strcase b)))))
				(start_list "listbox")
				(mapcar 'add_list  names)
				(end_list)
				(if(vl-member-if '(lambda(x) (= (strcase name) (strcase x))) names)
					(setq num (itoa (vl-position (strcase name) (mapcar 'strcase names))))
					(setq num (itoa (vl-position (strcase "0")(mapcar 'strcase names))))
				)
				(set_tile "listbox" num)
				(setq res (start_dialog))
				(unload_dialog id)
			)
		)
		(if (/= res 0)
			(progn
				(cond
					((= st "0")
						(setq ret (nth (atoi num) names))
					)
					((= st "1")
						(setq ret newname)
					)
				)
			)
		)
	)
	(defun OnAccept_Clicked(e)
		(setq newname (get_tile "userValue"))
		(setq st (get_tile "userInput"))
		(done_dialog 1)
	)
	(defun OnCancel_Clicked(e)
		(done_dialog 0)
	)
	(defun OnListBox_Clicked(e)
		(setq num e)
	)
	(defun OnUserInput_Clicked(e)
		(if (= e "1")
			(progn
				(mode_tile "listbox" 1)
				(mode_tile "userValue" 0)
			)
			(progn
				(mode_tile "listbox" 0)
				(mode_tile "userValue" 1)
			)
		)
	)
	(defun modifyName(ss lname)
		(if (not(tblobjname "LAYER" lname))
			(progn	
				(command "_layer" "n" lname "")
				(princ (strcat "\n" lname " は作成されました。"))
			)
		)
		(command "_.chprop" ss "" "la" lname "")
		(princ (strcat "\n" lname))
	)
	(defun *error*(s)
		(vla-EndUndoMark doc)
		(princ (strcat "\n" s))
		(princ)
	)
	(apply 'main nil)
)
