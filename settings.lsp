(vl-load-com)
;;setvar reg
(vl-catch-all-apply 'setvar '("commandpreview" 0))
(setvar "coords" 2)
(setvar "cursorsize" 100)
(setvar "dragmode" 2)
(vl-catch-all-apply 'setvar '("dtexted" 1))
(vl-catch-all-apply 'setvar '("dynmode" 1))
(vl-catch-all-apply 'setvar '("dynpicoords" 1))
(setvar "edgemode" 1)
(setvar "filedia" 1)
(vl-catch-all-apply 'setvar '("gripmultifunctional" 1))
(vl-catch-all-apply 'setvar '("hqgeom" 0))
(vl-catch-all-apply 'setvar '("layerdlgmode" 0))
(vl-catch-all-apply 'setvar '("linesmoothing" 0))
(vl-catch-all-apply 'setvar '("osoptions" 0))
;(vl-catch-all-apply 'setvar '("paletteopaque" 1))
(vl-catch-all-apply 'setvar '("pdfshx" 0))
(setvar "pickauto" 1)
(setvar "pickbox" 6)
(setvar "pickstyle" 0)
(setvar "polarang" (/ pi 12))
;(vl-catch-all-apply 'setvar '("propertypreview" 0))
(setvar "proxynotice" 0)
(vl-catch-all-apply 'setvar '("rollovertips" 0))
(vl-catch-all-apply 'setvar '("selectioncycling" 0))
(vl-catch-all-apply 'setvar '("selectioneffect" 0))
(vl-catch-all-apply 'setvar '("selectionpreview" 0))
(vl-catch-all-apply 'setvar '("selectionarea" 0))
(vl-catch-all-apply 'setvar '("secureload" 0))
(vl-catch-all-apply 'setvar '("texted" 1))
(vl-catch-all-apply 'setvar '("texteditmode" 1))
(vl-catch-all-apply 'setvar '("vtenable" 0))
(vl-catch-all-apply 'setvar '("xdwgfadectl" 0))
(vl-catch-all-apply 'setvar '("zoomfactor" 70))

;;setvar dwg
(setvar "angdir" 0)
(setvar "cecolor" "ByLayer")
(vl-catch-all-apply 'setvar '("clayer" "0"))
(setvar "celtscale" 1)
(setvar "celtype" "ByLayer")
(setvar "celweight" -1)
(setvar "dimassoc" 1)
(vl-catch-all-apply 'setvar '("draworderctl" 1))
(setvar "filletrad" 0)
(setvar "gridmode" 0)
(vl-catch-all-apply 'setvar '("layernotify" 0))
(setvar "mirrtext" 0)
(setvar "snapmode" 0)
(setvar "sortents" 127)
(setvar "ucsicon" 1)

;;setvar user
(vl-catch-all-apply 'setvar '("hpdlgmode" 1)) 
;(vl-catch-all-apply 'setvar '("hpquickpreview" 0)) 


;;setvar not-saved
(setvar "bindtype" 1)
(setvar "cmdecho" 1)
(setvar "hpname" "SOLID")

;;command
(defun c:b () (command "_break"))
(defun c:c () (command "_copy"))
(defun c:ca () (command "_laymcur"))
(defun c:cb () (command "_copybase"))
(defun c:ctl () (initcommandversion)(command "_copytolayer"))
(defun c:cu () (command "_laycur"))
(defun c:d () (command "_dist"))
(defun c:et () (command "_extend"))
(defun c:jt () (command "_justifytext"))
(defun c:n () (command "_matchprop"))
(defun c:nn () (command "_matchprop"))
(defun c:o () (command "_offset" "l" "s" "e" "n"))
(defun c:oo () (command "_offset" "l" "c" "e" "n"))
(defun c:ooo () (command "_offset" "l" "s" "e" "y"))
(defun c:pb () (command "_.pasteblock"))
(defun c:pua () (command "_.-purge" "_a" "*" "n"))
(defun c:pub () (command "_.-purge" "_b" "*" "n"))
(defun c:rr () (command "_.layerp"))
(defun c:t () (command "_trim"))
(defun c:xo () (command "_.xline" "o"))

;;wrapper command
(defun c:myMove (/ *error* osmode per)
	(defun *error*(s)
		(if per (setvar "osmode" (logior (getvar "osmode") per)))
		(princ)
	)
	(if (setq ss (ssget "_:L"))
		(progn
			(setq osmode (getvar "osmode"))
			(setq per (logand osmode 128))
			(setvar "osmode" (- osmode per))
			(initget 1)
			(setq res (getpoint "\nbase point:"))
			(setvar "osmode" (logior (getvar "osmode") per))
			(setq per nil)
			(command "_.move" ss "" "_non" res)
		)
	)	
	(princ)
)
;;a-z
(defun c:a3 ( / *error* sc pt)
	(defun *error*(s) (princ))
	(initget 7)
	(setq sc (getreal "\nscale:"))
	(initget 1)
	(setq pt (getpoint "\npt:"))
	(command "_.rectangle" "non" pt "non" (list (+ (car pt) (* sc 420.0)) (+ (cadr pt) (* sc 297.0))))
	(print (list (* sc 420) (* sc 297.0)))
	(princ)
)
(defun c:ag (/ *error* ss pt1 pt2 pt3 pt4)
	(if (setq ss (ssget "_:L"))
		(progn
			(initget 1)(setq pt1 (getpoint "\npt1:"))
			(initget 1)(setq pt2 (getpoint pt1 "\npt2:"))
			(initget 1)(setq pt3 (getpoint "\npt3:"))
			(initget 1)(setq pt4 (getpoint pt3 "\npt4:"))
			(command "._align" ss "" "_non" pt1 "_non" pt3 "_non" pt2 "_non" pt4 "" "")
		)
	)
	(princ)
)
(defun c:anb () (c:angBlock))
(defun c:anh () (c:angHatch))
(defun c:ant () (c:angText))
(defun c:at () (c:alignmentText))
(defun c:atot () (c:attdefToText))
(defun c:bgc () (c:bgcCtrl))
(defun c:bh ()
	(vl-catch-all-apply 'setvar '("hplayer" "."))
	(initcommandversion 2)
	(command "_.bhatch")
)
(defun c:cc () (c:stepCopy))
(defun c:ccc () (c:stackCopy))
(defun c:cm (/ *error*)
	(defun *error*(s)(command-s)(princ))
	(if (setq ss (ssget "_:L"))
		(progn
			(command "copy" ss "" pause "non" (getvar "lastpoint"))
			(command "move" "p" "" "non" (getvar "lastpoint"))
		)
	)
)
(defun c:cmr (/ *error* copied ss)
	(defun *error*(s)
		(if command-s (command-s) (command))
		(if copied
			(progn
				(setq i 0)
				(repeat (sslength ss)
					(entdel (ssname ss i))
					(setq i (1+ i))
				)
			)
		)
		(princ)
	)
	(if (setq ss (ssget "_:L"))
		(progn
			(command "copy" ss "" pause "non" (getvar "lastpoint"))
			(setq copied t)
			(command "move" "p" "" "non" (getvar "lastpoint") pause)
			(command "rotate" "p" "" (getvar "lastpoint"))
		)
	)
)
(defun c:cntb () (c:countBlock))
(defun c:cntt () (c:countText))
(defun c:con ()
	(command "-layer" "on" (getvar "clayer") "")
)
(defun c:eb () (c:easyBlock))
(defun c:ee () (c:easyExtend))
(defun c:es () (c:easySlice))
(defun c:ed () (c:extEditor))
(defun c:ga (/ *error* lname)
	(setvar "cmdecho" 0)
	(if (setq lname (getstring "\nlname:"))(command "_.layer" "m" lname ""))
	lname
)
(defun c:gc () (c:changeColor))
(defun c:gr () (c:changeLayer))
(defun c:gt () (c:changeLinetype))
(defun c:hm () (c:hatchMove))
(defun c:llt ()
	(setvar "cmdecho" 1)
	(command "_.linetype" "l" "JIS*" "acadiso.lin")
	(while (= (getvar "cmdactive") 1) (command ""))
	(princ)
)
(defun c:m () (c:mymove))
(defun c:mm () (c:stepMove))
(defun c:para () (c:parallelogram))
(defun c:pj (/ *error* ss peditaccept)
	(setvar "cmdecho" 0)
	(if (setq ss (ssget "_:L" '((0 . "LWPOLYLINE,LINE,ARC"))))
		(progn
			(setq peditaccept (getvar "peditaccept"))
			(setvar "peditaccept" 1)
			(command "._pedit" "m" ss "" "j" "" "")
			(setvar "peditaccept" peditaccept)
		)
	)
)
(defun c:scv () (c:verticalscale))
(defun c:sf () (c:setScaleFactor))
(defun c:sqr (/ *error*)
	(defun *error* (s) (princ))
	(initget 1)
	(setq pt (getpoint "\npt:"))
	(initget 1)
	(setq len (getreal "\nlen:"))
	(command "_polygon" 4 "non" pt "c" (* 0.5 len))
	(princ)
)
(defun c:srt () (c:srtObj))
(defun c:tc () (c:copyTextStr))
(defun c:tt () (c:textEditAd))
(defun c:xt () (c:exchangeText))

;;draworder
(defun c:dda () (c:draworderAuto))
(defun c:ddd () (c:draworderLayer))
(defun c:ddb () (c:draworderLayer_args "B"))
(defun c:ddf () (c:draworderLayer_args "F"))

;;layertable
(defun c:rcss () (c:chBylayerTColor))

;;pviewport
(defun c:ppn () (c:pviewportPan))
(defun c:ptm () (c:pviewportToModel))
(defun c:v () (c:pviewportLock))
(defun c:vl () (c:pviewportLock))

;;layer
(defun c:ra () (c:layAllOn))
(defun c:fa () (c:layAllOff))
(defun c:rss () (c:laySSOn))
(defun c:fss () (c:laySSOff))
(defun c:rs () (c:layPickNestOn))
(defun c:rn () (c:layPickNestOn))
(defun c:fs () (c:layPickNestOff))
(defun c:fn () (c:layPickNestOff))
(defun c:rev () (c:layRev))

;;filter
(defun c:fb() (ssget '((0 . "INSERT"))))
(defun c:fci() (ssget '((0 . "CIRCLE"))))
(defun c:fd() (ssget '((0 . "DIMENSION"))))
(defun c:fh() (ssget '((0 . "HATCH"))))
(defun c:fli() (ssget '((0 . "LINE"))))
(defun c:fmt() (ssget '((0 . "MTEXT"))))
(defun c:fp() (ssget '((0 . "POINT"))))
(defun c:fpl() (ssget '((0 . "LWPOLYLINE"))))
(defun c:fso() (ssget '((0 . "3DSOLID"))))
(defun c:ft() (ssget '((0 . "TEXT"))))

;;grip
(defun c:cg () (c:copyGrip))
(defun c:g () (c:grip))

;;startapp
(defun c:calc () (startapp "calc"))
(defun c:df() (startapp "explorer" (getvar "dwgprefix")))
(defun c:tf() (startapp "explorer" (getvar "tempprefix")))

;;hojo line
(defun c:rayU (/ *error*)
	(if (setq pt (getpoint "\npt:"))(command "_.ray" "_non" pt "_non" "@0,1" ""))
)
(defun c:rayD (/ *error*)
	(if (setq pt (getpoint "\npt:"))(command "_.ray" "_non" pt "_non" "@0,-1" ""))
)
(defun c:rayL (/ *error*)
	(if (setq pt (getpoint "\npt:"))(command "_.ray" "_non" pt "_non" "@-1,0" ""))
)
(defun c:rayR (/ *error*)
	(if (setq pt (getpoint "\npt:"))(command "_.ray" "_non" pt "_non" "@1,0" ""))
)
(defun c:xx (/ *error*)
	(if (setq pt (getpoint "\npt:"))(command "_.xline" "_non" pt "_non" "@1,0" ""))
)
(defun c:yy (/ *error*)
	(if (setq pt (getpoint "\npt:"))(command "_.xline" "_non" pt "_non" "@0,1" ""))
)
(defun c:xy (/ *error*)
	(if (setq pt (getpoint "\npt:"))
		(command "_.xline" "_non" pt "_non" "@1,0" "_non" "@0,1" "")
	)
)
;;restart
(defun c:res () (load "acaddoc.lsp" nil))

;;memo
;(dictremove (namedobjdict) "AcSheetSetData")
