(defun utf8load (fn / *error* str)
	(vl-load-com)
	(setq fn (findfile fn))
	(setq str (utf8loader-Readall fn))
	(if (setq str (utf8loader-Decode str))
		(progn
			;;(eval (read (strcat "(progn\n" str "\n)" )))
			(setq temp (strcat (getvar "tempprefix") (vl-filename-base fn) ".lsp"))
			(utf8loader-write str temp)
			(load temp nil)
		)
		(progn
			;;(princ "\n can not UTF-8 decoding. using load function.")
			(load fn nil)
		)
	)
)
(defun utf8load_dialog(fn / *error* str)
	(vl-load-com)
	(setq fn (findfile fn))
	(setq str (utf8loader-readall fn))
	(if (setq str (utf8loader-decode str))
		(progn
			(setq temp (strcat (getvar "tempprefix") (vl-filename-base fn) ".dcl"))
			(utf8loader-write str temp)
			(load_dialog temp)
		)
		(progn
			;;(princ "\n can not UTF-8 decoding. using load_dialog function.")
			(load_dialog fn)
		)
	)
)
(defun utf8loader-write (str fn / dsc)
	(setq dsc (open fn "w"))
	(write-line str dsc)
	(close dsc)
	fn
)
(defun utf8loader-readall (fn / *error* dsc res lst)
	(setq dsc (open fn "r"))
	(while (setq res (read-line dsc))
		(setq lst (cons "\n" (cons res lst)))
	)
	(close dsc)
	(apply 'strcat (reverse (cdr lst)))
)
(defun utf8loader-decode (str / *error* isUtf8 ret lst buff tmp ret)
	(defun main ()
		(setq b00000000   0)
		(setq b10000000 128)
		(setq b11000000 192)
		(setq b11100000 224)
		(setq b11110000 240)
		(setq b11111000 248)
		(setq isUtf8 t)
		(setq lst (vl-string->list str))
		(if
			(and
				(= (car lst) 239)
				(= (cadr lst) 187)
				(= (caddr lst) 191)
			)
			(progn
				;;(princ "\nBOM skip")
				(setq lst (cdddr lst))
			)
		)
		(while (and isUtf8 lst)
			(cond
				;1byte
				((= b00000000 (logand b10000000 (car lst))) 
					(setq buff (cons (chr (car lst)) buff))
					(setq lst (cdr lst))
				)
				;not utf8
				((= b10000000 (logand b11000000 (car lst))) 
					(setq isUtf8 nil)
				)
				;2byte code
				((= b11000000 (logand b11100000 (car lst))) 
					(setq tmp (list (car lst) (cadr lst)))
					(setq tmp (encoding2 tmp))
					(setq buff (cons tmp buff))
					(setq lst (cddr lst))
				)
				;3byte code
				((= b11100000 (logand b11110000 (car lst)))
					(setq tmp (list (car lst) (cadr lst) (caddr lst)))
					(setq tmp (encoding3 tmp))
					(setq buff (cons tmp buff))
					(setq lst (cdddr lst))
				)
				;4Byte code
				((= b11110000 (logand b11111000 (car lst)))
					(setq tmp (list (car lst) (cadr lst) (caddr lst) (cadddr lst)))
					(setq tmp (encoding4 tmp))
					(setq buff (cons tmp buff))
					(setq lst (cddddr lst))
				)
				(t
					(setq isUtf8 nil)
				)
			)
		)
		(if isUtf8
			(progn
				(setq buff (reverse buff))
				(setq ret (apply 'strcat buff))
			)
			(progn
				(setq ret nil)
			)
		)
		ret
	)
	(defun encoding2 (moji)
		(setq bit1-6 (logand (cadr moji) 63))
		(setq bit7-11 (logand (car moji) 31))
		(setq bits (logior (lsh bit7-11 6) bit1-6))
		(strcat "\\\\u+" (dechex bits))
	)
	(defun encoding3 (moji)
		(setq bit1-6 (logand (caddr moji) 127))
		(setq bit7-12 (logand (cadr moji) 127))
		(setq bit13-16 (logand (car moji) 15))
		(setq bit1-8 (logior bit1-6 (lsh (logand bit7-12 3) 6)))
		(setq bit9-16 (logior (lsh (logand bit13-16 15) 4) (lsh (logand bit7-12 (+ 4 8 16 32)) -2)))
		(setq bit1-16 (logior (lsh bit9-16 8) bit1-8))
		(strcat "\\\\u+" (dechex bit1-16))
	)
	(defun encoding4 (moji)
		(setq aaa nil)
		(setq int32 (+ (lsh (car moji) 24)))
		(setq bit1-6 (logand (cadddr moji) 127))
		(setq bit7-12 (logand (caddr moji) 127))
		(setq bit13-18 (logand (cadr moji) 127))
		(setq bit19-21 (logand (car moji) 7))
		(setq int (+ bit1-6 (lsh bit7-12 6) (lsh bit13-18 12) (lsh bit19-21 15)))
		(setq x10000 65536)
		(setq int (- int x10000))
		(setq xD800 55296)
		(setq xDC00 56320)
		(setq utf16hi (+ (lsh int -10) xD800))
		(setq utf16low (+ (logand int 1023)xDC00))
		(strcat "\\\\u+" (dechex utf16hi) "\\\\u+" (dechex utf16low))
	)
	(defun dechex(num / loop n str)
		(setq loop t str "")
		(while loop
			(setq n (logand num 15))
			(cond
				((<= n 9) (setq n (itoa n)))
				((= n 10) (setq n "A"))
				((= n 11) (setq n "B"))
				((= n 12) (setq n "C"))
				((= n 13) (setq n "D"))
				((= n 14) (setq n "E"))
				((= n 15) (setq n "F"))
			)
			(setq str (strcat n str))
			(setq num (lsh num -4))
			(if (= num 0)(setq loop nil))
		)
		(while (< (strlen str) 4)
			(setq str (strcat "0" str))
		)
		str
	)
	(main)
)
(defun utf8demandLoad (fileName symList)
	(vl-load-com)
	(utf8demandLoad-varidate symList)
)
(defun utf8demandLoad-varidate(e / fnc)
	(if (= (type e) 'LIST)
		(if (apply 'and (mapcar 'vl-symbolp e))
			(utf8demandLoad-define e)
			(mapcar 'utf8demandLoad-varidate e)
		)
	)
)
(defun utf8demandLoad-define(e /)
	(eval
		(list 'defun (car e) (cdr e)
			(list 'utf8demandLoad-override (vl-princ-to-string e)fileName)
		)
	)
)
(defun utf8demandLoad-override (s f / *error* sym surb ff)
	(defun *error*(s) (princ s)(set sym surb))
	(set 'sym (car (read s)))
	(set 'surb (eval sym))
	(set sym nil)
	(if (setq ff (findfile f))
		(progn
			(princ (strcat "\n" ff ""))
			(if utf8load (utf8load ff)(load ff nil))
			(if (eval sym)
				(eval(append (list sym) (cdr (read s))))
				(progn
					(princ (strcat "\n" (vl-symbol-name(car (read s))) " is not defined in \"" f "\"."))
					(set sym surb)
					(princ)
				)
			)
		)
		(progn
			(princ (strcat "\n\"" f "\" is not found."))
			(set sym surb)
			(princ)
		)
	)
)
